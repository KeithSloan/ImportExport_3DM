# -*- coding: utf-8 -*-
# make_3dm_gallery — batch-import every .3dm under a directory and build a
# self-contained HTML gallery of the imported results, for eyeballing import
# quality across a folder of Rhino sample files.
#
# Usage (FreeCAD GUI): Macro -> Macros... -> select this file -> Execute.
# It prompts for a directory, renders each .3dm to a thumbnail, and writes
# <dir>/import_gallery/gallery.html (open it in a browser).
#
# Notes:
#  - Uses this addon's import3DM importer.
#  - import3DM >= 0.5.0 guards the OCCT sew (ImportSewFaceLimit, default 8), so
#    a pathological file such as v5_ring.3dm imports as a compound instead of
#    hanging the macro. SKIP is kept for genuinely un-importable files.
#  - Objects on invisible Rhino layers are hidden on import
#    (ImportRespectLayerVisibility), so thumbnails show what Rhino shows.
#  - A blank thumbnail is expected for files with no geometry (empty files,
#    light/viewport-only files) — the Report View explains why.

import os, glob, base64, html, traceback
import FreeCAD, FreeCADGui
from PySide import QtGui

SKIP = set()          # basenames to skip (e.g. {"broken.3dm"})
THUMB_W, THUMB_H = 480, 360

# Pin the import preferences the gallery depends on so thumbnails are
# reproducible regardless of the user's saved preferences.
def _pin_prefs(mod):
    ns = "User parameter:BaseApp/Preferences/Mod/ImportExport_3DM"
    p = FreeCAD.ParamGet(ns)
    p.SetBool("ImportRespectLayerVisibility", True)   # hide off-layer objects
    p.SetBool("ImportCreateGroups", True)
    p.SetBool("ImportMakeShell", False)
    p.SetBool("ImportNativePrimitives", True)
    p.SetInt("ImportSewFaceLimit", 8)                 # guarded sew (no hangs)

def _import3DM():
    import importlib
    try:
        import import3DM as m
    except Exception:
        here = os.path.join(FreeCAD.getUserAppDataDir(), "Mod", "ImportExport_3DM",
                            "freecad", "importExport3DM")
        import sys
        if here not in sys.path: sys.path.insert(0, here)
        import import3DM as m
    return m

def _anchor_degenerate_points(doc):
    """FreeCAD's Points view culls a point feature whose points all sit at a
    single location (empty bounding box), so such imports would render blank in
    a thumbnail.  Add a small temporary sphere anchor at each such location so
    the point shows; the sphere lives only in this throw-away gallery document.
    Radius ~0.6% of the model diagonal, so it reads as a point marker, not as
    stray cubes (as a 4%-of-diagonal box did around the soccer ball)."""
    import Part
    try:
        D = 0.0
        for o in doc.Objects:
            if o.TypeId == "Part::Feature" and o.Shape and not o.Shape.isNull():
                bb = o.Shape.BoundBox
                if bb.XLength < 1e90:
                    D = max(D, bb.DiagonalLength)
        if D <= 0:
            D = 2.0
        r = D * 0.006
        for o in doc.Objects:
            if o.TypeId != "Points::Feature":
                continue
            try:
                pts = [FreeCAD.Vector(p) for p in o.Points.Points]
            except Exception:
                continue
            if not pts:
                continue
            xs = [p.x for p in pts]; ys = [p.y for p in pts]; zs = [p.z for p in pts]
            diag = ((max(xs) - min(xs)) ** 2 + (max(ys) - min(ys)) ** 2
                    + (max(zs) - min(zs)) ** 2) ** 0.5
            if diag > 1e-6:
                continue                     # spread points render normally
            try:
                if not o.ViewObject.Visibility:
                    continue                 # points on hidden Rhino layers
            except Exception:
                pass
            for p in pts:
                s = doc.addObject("Part::Feature", "PtAnchor")
                s.Shape = Part.makeSphere(r, p)
    except Exception:
        pass


def _visible_content(doc):
    """True when the doc has any visible, non-origin geometry (incl. anchors)."""
    try:
        for o in doc.Objects:
            if o.TypeId in ("App::Origin", "App::Line", "App::Plane",
                            "App::Point", "App::Part"):
                continue
            if not o.ViewObject.Visibility:
                continue
            if o.TypeId in ("Mesh::Feature", "Points::Feature"):
                return True
            if o.TypeId.startswith("Part::") and hasattr(o, "Shape"):
                sh = o.Shape
                if sh is not None and not sh.isNull():
                    bb = sh.BoundBox
                    if bb.XLength < 1e90 and bb.XLength > 0:
                        return True
    except Exception:
        return True
    return False

def _write_no_geometry_png(path):
    """Render a white thumbnail with 'No geometry to import' text for files
    whose import yields nothing (empty files, view/light-only files)."""
    from PySide import QtGui
    try:
        img = QtGui.QImage(THUMB_W, THUMB_H, QtGui.QImage.Format_RGB32)
        img.fill(QtGui.QColor("white"))
        p = QtGui.QPainter(img)
        p.setPen(QtGui.QColor(140, 140, 140))
        f = p.font()
        f.setPointSize(18)
        p.setFont(f)
        p.drawText(img.rect(), QtGui.Qt.AlignCenter,
                   "No geometry to import")
        p.end()
        img.save(path)
    except Exception:
        pass

def render_one(mod, path, thumbdir):
    name = os.path.basename(path)
    thumb = os.path.join(thumbdir, os.path.splitext(name)[0].replace(" ", "_") + ".png")
    doc = FreeCAD.newDocument("gallery_tmp")
    status = "OK"
    try:
        fi = mod.File3dm(path)
        fi.parse_objects(doc)
        doc.recompute()
        # hide App::Part origins / datum planes so fitAll frames real geometry
        for o in doc.Objects:
            if o.TypeId in ("App::Origin", "App::Plane", "App::Line"):
                try: o.ViewObject.Visibility = False
                except Exception: pass
        _anchor_degenerate_points(doc)
        doc.recompute()
        if not _visible_content(doc):
            FreeCAD.Console.PrintMessage(
                "  %s: no geometry to display (empty or non-geometric file)\n" % name)
            _write_no_geometry_png(thumb)
            status = "OK (no geometry)"
        else:
            FreeCADGui.updateGui()
            av = FreeCADGui.ActiveDocument.ActiveView
            av.viewIsometric(); av.fitAll()
            av.saveImage(thumb, THUMB_W, THUMB_H, "White")
    except Exception as e:
        status = "ERR " + type(e).__name__
        FreeCAD.Console.PrintError("  %s: %s\n" % (name, e))
    finally:
        FreeCAD.closeDocument(doc.Name)
    return name, thumb if os.path.exists(thumb) else None, status

def build_html(rows, out):
    P = ['<!doctype html><meta charset="utf-8"><title>3DM import gallery</title>',
         '<style>body{font-family:system-ui,sans-serif;background:#f5f5f7;margin:0}'
         'h1{font-size:17px;padding:16px 20px;background:#fff;border-bottom:1px solid #ddd;margin:0}'
         '.grid{display:grid;grid-template-columns:repeat(auto-fill,minmax(200px,1fr));gap:12px;padding:16px}'
         '.c{background:#fff;border:1px solid #e0e0e0;border-radius:8px;overflow:hidden}'
         '.c img{width:100%;height:150px;object-fit:contain;background:#fafafa;display:block}'
         '.cap{padding:6px 8px;font-size:11px;word-break:break-all;border-top:1px solid #eee}'
         '.err{color:#b00}</style>',
         '<h1>3DM import gallery — %d files</h1><div class="grid">' % len(rows)]
    for name, thumb, status in rows:
        cls = ' class="err"' if status.startswith("ERR") else ''
        if thumb:
            b = base64.b64encode(open(thumb, "rb").read()).decode()
            img = '<img src="data:image/png;base64,%s">' % b
        else:
            img = '<div style="height:150px"></div>'
        P.append('<div class="c">%s<div class="cap"%s>%s<br>%s</div></div>'
                 % (img, cls, html.escape(name), html.escape(status)))
    P.append('</div>')
    open(out, "w").write("\n".join(P))

def run():
    start = FreeCAD.getUserAppDataDir()
    d = QtGui.QFileDialog.getExistingDirectory(None, "Folder of .3dm files to gallery", start)
    if not d:
        return
    files = sorted(glob.glob(os.path.join(d, "**", "*.3dm"), recursive=True))
    files = [f for f in files if os.path.basename(f) not in SKIP]
    if not files:
        FreeCAD.Console.PrintMessage("No .3dm files found under %s\n" % d)
        return
    outdir = os.path.join(d, "import_gallery")
    os.makedirs(outdir, exist_ok=True)
    mod = _import3DM()
    _pin_prefs(mod)
    rows = []
    for i, p in enumerate(files):
        FreeCAD.Console.PrintMessage("  gallery %d/%d: %s\n" % (i + 1, len(files), os.path.basename(p)))
        rows.append(render_one(mod, p, outdir))
    out = os.path.join(outdir, "gallery.html")
    build_html(rows, out)
    FreeCAD.Console.PrintMessage("Gallery written: %s\n" % out)
    try:
        QtGui.QDesktopServices.openUrl("file://" + out)
    except Exception:
        pass

run()
